# SPDX-FileCopyrightText: 2024 Ondsel <development@ondsel.com>
#
# SPDX-License-Identifier: LGPL-2.0-or-later

import FreeCADGui as Gui

import lens_command
import WorkspaceView


lens_command.start_mdi_tab()
if WorkspaceView.wsv:
    url = WorkspaceView.wsv.get_lens_url()
    WorkspaceView.wsv.handle_lens_url(url)
